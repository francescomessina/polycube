module router {
  yang-version 1.1;
  namespace "http://polycube.network/router";
  prefix "router";

  import polycube-base { prefix "basemodel"; }

  import ietf-inet-types { prefix "inet"; }
  import ietf-yang-types { prefix "yang";  }

  organization "Polycube open source project";
  description "YANG data model for the Polycube Router service";

  basemodel:service-description "Router Service";
  basemodel:service-version "2.0";
  basemodel:service-name "router";
  basemodel:service-min-kernel-version "4.15.0";

  extension cli-example {
    argument "value";
    description "A sample value used by the CLI generator";
  }

  uses "basemodel:base-yang-module" {
     augment ports {
       leaf ip {
        type inet:ipv4-address;
        description "IP address of the port";
        router:cli-example "207.46.130.1";
      }

      leaf netmask {
        type inet:ipv4-address;
        description "Netmask of the port";
        router:cli-example "255.255.255.0";
      }

      list secondaryip {
        description "Secondary IP address for the port";
        key "ip netmask";
        leaf ip {
          type inet:ipv4-address;
          mandatory true;
          description "Seconadary IP address of the port";
          router:cli-example "207.46.131.1";
        }

        leaf netmask {
          type inet:ipv4-address;
          mandatory true;
          description "Secondary netmask of the port";
          router:cli-example "255.255.255.0";
        }
      }

      leaf mac {
        type yang:mac-address;
        description "MAC address of the port";
        router:cli-example "B3:23:45:F5:3A";
      }
    }
  }

  list route {
    key "network netmask nexthop";
    description "Entry associated with the routing table";
    leaf network {
      type inet:ipv4-address;
      mandatory true;
      description "Destination network IP";
      router:cli-example "123.13.34.0";
    }

    leaf netmask {
      type inet:ipv4-address;
      mandatory true;
      description "Destination network netmask";
      router:cli-example "255.255.255.0";
    }

    leaf nexthop {
      type inet:ipv4-address;
      mandatory true;
      description "Next hop; if destination is local will be shown 'local' instead of the ip address";
      router:cli-example "123.14.23.3";
    }

    leaf interface {
      type string;
      config false;
      description "Outgoing interface";
      router:cli-example "port2";
    }

    leaf pathcost {
      type int32;
      default 1;
      description "Cost of this route";
      router:cli-example "10";
    }
  }

  list arp-entry {
    key "address";
    description "Entry associated with the ARP table";
    leaf address {
      type inet:ip-prefix;
      mandatory true;
      description "Destination IP address";
      router:cli-example "123.13.34.0";
    }

    leaf mac {
      type string;
      mandatory true;
      description "Destination MAC address";
      router:cli-example "C5:13:2D:36:27:9B";
    }

    leaf interface {
      type string;
      mandatory true;
      description "Outgoing interface";
      router:cli-example "port2";
    }
  }
}
